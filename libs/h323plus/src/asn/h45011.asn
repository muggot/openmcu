Call-Intrusion-Operations
{
  itu-t recommendation h 450 11 version1(0) call-intrusion-operations(0)
}

DEFINITIONS AUTOMATIC TAGS ::=
BEGIN

  IMPORTS CallIdentifier FROM H225 -- H323-MESSAGES see H.225.0

          MixedExtension, undefined FROM H4504 -- Call-Hold-Operations 
          {
            itu-t recommendation h 450 4 version1(0) call-hold-operations(0)
          }

          notAvailable, supplementaryServiceInteractionNotAllowed FROM H4501 -- H4501-General-Error-List
          {
            itu-t recommendation h 450 1 version1(0) general-error-list (1)
          }

          callWaiting FROM H4506 -- Call-Waiting-Operations 
          {
            itu-t recommendation h 450 6 version1(0) call-waiting-operations(0)
          }

          cfbOverride, remoteUserAlerting FROM H45010 -- Call-Offer-Operations 
          {
            itu-t recommendation h 450 10 version1(0) call-offer-operations(0)
          };


  H323CallIntrusionOperations ::= ENUMERATED
  {
    callIntrusionRequest(43),
    callIntrusionGetCIPL(44),
    callIntrusionIsolate(45),
    callIntrusionForcedRelease(46),
    callIntrusionWOBRequest(47),
    callIntrusionSilentMonitor(116),
    callIntrusionNotification(117)
    -- cfbOverride(49),         Imported from H.450.10
    -- remoteUserAlerting(115), Imported from H.450.10
    -- callWaiting(105)         Imported from H.450.6
  } -- callWaiting is only used for interaction with Call Transfer --

  CIRequestArg ::= SEQUENCE
  {
    ciCapabilityLevel CICapabilityLevel,
    argumentExtension SEQUENCE SIZE (0..255) OF MixedExtension OPTIONAL,
    ...
  }

  CIRequestRes ::= SEQUENCE
  {
    ciStatusInformation CIStatusInformation,
    resultExtension     SEQUENCE SIZE (0..255) OF MixedExtension OPTIONAL,
    ...
  }

  CIGetCIPLOptArg ::= SEQUENCE
  {
    argumentExtension SEQUENCE SIZE (0..255) OF MixedExtension  OPTIONAL,
    ...
  }

  CIGetCIPLRes ::= SEQUENCE
  {
    ciProtectionLevel         CIProtectionLevel,
    silentMonitoringPermitted NULL OPTIONAL,
    resultExtension           SEQUENCE SIZE (0..255) OF MixedExtension OPTIONAL,
    ...
  }

  CIIsOptArg ::= SEQUENCE
  {
    argumentExtension SEQUENCE SIZE (0..255) OF MixedExtension OPTIONAL,
    ...
  }

  CIIsOptRes ::= SEQUENCE
  {
    resultExtension SEQUENCE SIZE (0..255) OF MixedExtension OPTIONAL,
   ...
  }

  CIFrcRelArg ::= SEQUENCE
  {
    ciCapabilityLevel CICapabilityLevel,
    argumentExtension SEQUENCE SIZE (0..255) OF MixedExtension OPTIONAL,
    ...
  }

  CIFrcRelOptRes ::= SEQUENCE
  {
    resultExtension SEQUENCE SIZE (0..255) OF MixedExtension OPTIONAL,
    ...
  }

  CIWobOptArg ::= SEQUENCE
  {
    argumentExtension SEQUENCE SIZE (0..255) OF MixedExtension  OPTIONAL,
    ...
  }

  CIWobOptRes ::= SEQUENCE
  {
    resultExtension SEQUENCE SIZE (0..255) OF MixedExtension OPTIONAL,
    ...
  }


  CISilentArg ::= SEQUENCE
  {
    ciCapabilityLevel CICapabilityLevel,
    specificCall      CallIdentifier OPTIONAL,
    argumentExtension SEQUENCE SIZE (0..255) OF MixedExtension OPTIONAL,
    ...
  }

  CISilentOptRes ::= SEQUENCE
  {
    resultExtension SEQUENCE SIZE (0..255) OF MixedExtension OPTIONAL,
    ...
  }

  CINotificationArg ::= SEQUENCE
  {
    ciStatusInformation CIStatusInformation,
    argumentExtension   SEQUENCE SIZE (0..255) OF MixedExtension OPTIONAL,
    ...
  }


  CICapabilityLevel ::= INTEGER --(1..3)
  {
    intrusionLowCap(1),
    intrusionMediumCap(2),
    intrusionHighCap(3)
  }

  CIProtectionLevel ::= INTEGER --(0..3)
  { 
    lowProtection(0),
    mediumProtection(1),
    highProtection(2),
    fullProtection(3)
  }

  CIStatusInformation ::= CHOICE
  {
    callIntrusionImpending NULL,
    callIntruded           NULL,
    callIsolated           NULL,
    callForceReleased      NULL,
    callIntrusionComplete  NULL,
    callIntrusionEnd       NULL,
    ...
  }

  CallIntrusionErrors ::= ENUMERATED
  {
    notBusy(1009),                -- used when the called user is not busy
    temporarilyUnavailable(1000), -- used when conditions for invocation of SS-CI are momentarily not met
    notAuthorized(1007)           -- used when a SS-CI request is rejected because of insufficient CICL or 
                                  -- if silent monitoring is not permitted
  }

END -- of Call-Intrusion-Operations
