Message-Waiting-Indication-Operations
{
  itu-t recommendation h 450 7 version1(0)  message-waiting-operations(0)
} 

DEFINITIONS AUTOMATIC TAGS ::=
BEGIN
	
  IMPORTS Extension FROM H4501 -- Manufacturer-specific-service-extension-definition
          {
            itu-t recommendation h 450 1 version1(0) msi-definition(18)
          }

          userNotSubscribed, invalidServedUserNumber, basicServiceNotProvided FROM H4501 -- H4501-General-Error-List
          {
            itu-t recommendation h 450 1 version1(0) general-error-list(1)
          }

  EndpointAddress FROM H4501 -- Addressing-Data-Elements 
  {
    itu-t recommendation h 450 1 version1(0)  addressing-data-elements(9)
  }

  MixedExtension FROM H4504 -- Call-Hold-Operations
  {
    itu-t recommendation h 450 4 version1(0) call-hold-operations(0)
  };

  H323-MWI-Operations ::= ENUMERATED
  {
    mwiActivate(80),
    mwiDeactivate(81),
    mwiInterrogate(82)
  }
	
  MWIActivateArg ::= SEQUENCE
  {
    servedUserNr  EndpointAddress,
    basicService  BasicService,
    msgCentreId   MsgCentreId OPTIONAL,
    nbOfMessages  NbOfMessages OPTIONAL,
    originatingNr EndpointAddress OPTIONAL,
    timestamp     TimeStamp OPTIONAL,
    priority      INTEGER (0..9) OPTIONAL, -- the value 0 means the highest priority and 9 the lowest
    extensionArg  SEQUENCE SIZE(0..255) OF MixedExtension OPTIONAL,
    ...
  }
	
  DummyRes ::= SEQUENCE SIZE(0..255) OF MixedExtension
	
  MWIDeactivateArg ::= SEQUENCE
  {
    servedUserNr EndpointAddress,
    basicService BasicService,
    msgCentreId  MsgCentreId OPTIONAL,
    callbackReq  BOOLEAN OPTIONAL,
    extensionArg SEQUENCE SIZE(0..255) OF MixedExtension OPTIONAL,
    ...
  }
	
  MWIInterrogateArg ::= SEQUENCE
  {
    servedUserNr EndpointAddress,
    basicService BasicService,
    msgCentreId  MsgCentreId OPTIONAL,
    callbackReq  BOOLEAN OPTIONAL,
    extensionArg SEQUENCE SIZE(0..255) OF MixedExtension OPTIONAL,
    ...
  }
	
  MWIInterrogateRes ::= SEQUENCE SIZE(1..64) OF MWIInterrogateResElt
	
  MWIInterrogateResElt ::= SEQUENCE
  {
    basicService  BasicService,
    msgCentreId   MsgCentreId OPTIONAL,
    nbOfMessages  NbOfMessages OPTIONAL,
    originatingNr EndpointAddress OPTIONAL,
    timestamp     TimeStamp OPTIONAL,
    priority      INTEGER (0..9) OPTIONAL, -- the value 0 means the highest priority and 9 the lowest
    extensionArg  SEQUENCE SIZE(0..255) OF MixedExtension OPTIONAL,
    ...
  }
	
  MsgCentreId ::= CHOICE
  {
    -- only partyNumber provides a callable identification
    integer       INTEGER (0..65535),
    partyNumber   EndpointAddress,
    numericString NumericString (SIZE (1..10))
  }
	
  NbOfMessages ::= INTEGER (0..65535)
						
  TimeStamp ::= GeneralizedTime (SIZE (12..19))
  -- a VisibleString representation of date and time following ISO 8601 
  -- containing:	
  --    - the  (local) date in 8 digits (YYYYMMDD),
  --    - followed by (local) time of day in 4 or 6 digits (HHMM[SS]),
  --    - optionally followed by the letter "Z" or by a local time differential 
  --      from UTC time in 5 digits ("+"HHMM or "-"HHMM);
  -- Examples:
  --    1) 19970621194530, meaning 21 June 1997, 19:45:30;
  --    2) 19970621194530Z, meaning the same as 1);
  --    3) 19970621194530-0500, meaning the same as 1), 
  --       5 hours retarded in relation to UTC time

  MessageWaitingIndicationErrors ::= ENUMERATED
  {
    notActivated(31),
    undefined(2002),
    invalidMsgCentreId(1018) 		
  }
	
  BasicService ::= ENUMERATED
  {
    allServices(0),
    speech(1),
    unrestrictedDigitalInformation(2),
    audio3100Hz(3),
    telephony(32),
    teletex(33),
    telefaxGroup4Class1(34),
    videotexSyntaxBased(35),
    videotelephony(36)
  }

END -- of Message-Waiting-Indication-Operations
